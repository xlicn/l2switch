module packet-security {

    yang-version 1;
    namespace "urn:opendaylight:packet:security";
    prefix "packet-security";

    description
        "This module contains the switch of canSelfDestruct.";

    revision 2017-12-03 {
        description "Initial module draft.";
    }

    container SelfDestructSwitch{
        leaf switch{
            type boolean;
            default false;
        }

    }

}
